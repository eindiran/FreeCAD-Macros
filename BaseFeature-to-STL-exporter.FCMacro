'''
BaseFeature-to-STL-exporter.FCMacro

FreeCAD macro to export all top-level 'BaseFeature' objects as STL files.
'''
import FreeCAD
import Mesh

save_dir = '~/' # Update this to be the correct save directory for your project. It should end in the path separator.

for obj in FreeCAD.ActiveDocument.Objects:
    if obj.PropertiesList[0] == 'BaseFeature':
        Mesh.export([obj], '{}{}-{}.step'.format(save_dir, FreeCAD.ActiveDocument.Name, obj.Name))
print('STL Export Complete!')
