'''
BaseFeature-to-STEP-exporter.FCMacro

FreeCAD macro to export all top-level 'BaseFeature' objects as STEP files.
'''
import FreeCAD
import ImportGui

save_dir = '~/' # Update this to be the correct save directory for your project. It should end in the path separator.

for obj in FreeCAD.ActiveDocument.Objects:
    if obj.PropertiesList[0] == 'BaseFeature':
        ImportGui.export([obj], '{}{}-{}.step'.format(save_dir, FreeCAD.ActiveDocument.Name, obj.Name))
print('STEP Export Complete!')
