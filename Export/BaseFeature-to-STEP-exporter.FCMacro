'''
BaseFeature-to-STEP-exporter.FCMacro

FreeCAD macro to export all top-level 'BaseFeature' objects as STEP files.
'''
import FreeCAD
import ImportGui

save_dir = '~/' # Update this to be the correct save directory for your project. It should end in the path separator.

for obj in FreeCAD.ActiveDocument.Objects:
    if 'BaseFeature' in set(obj.PropertiesList):
        # ImportGui.export() wants a sequence, so wrap the object in a list:
        ImportGui.export([obj], f'{save_dir}{FreeCAD.ActiveDocument.Name}-{obj.Name}.step')
print('STEP Export Complete!')
